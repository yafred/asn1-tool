-- PASS
My-Module1 { iso member-body(2) f(250) type(1) module1(1) } DEFINITIONS ::= 
BEGIN 
EXPORTS My-Integer;

My-Integer ::= INTEGER 
END


My-Module2 { iso member-body(2) f(250) type(1) module2(2) } DEFINITIONS ::= 
BEGIN 
IMPORTS My-Integer FROM  My-Module1 { iso member-body(2) f(250) type(1) module1(1) };

My-SubInteger ::= My-Integer 
END
