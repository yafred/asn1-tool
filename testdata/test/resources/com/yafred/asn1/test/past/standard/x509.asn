-- simplified version of rfc5280
--> integerSize huge

X509  DEFINITIONS EXPLICIT TAGS ::=

BEGIN

Certificate  ::=  SEQUENCE  {
     tbsCertificate       TBSCertificate,
     signatureAlgorithm   AlgorithmIdentifier,
     signature            BIT STRING  
     }

TBSCertificate  ::=  SEQUENCE  {
     version         [0]  Version DEFAULT v1,
     serialNumber         CertificateSerialNumber,
     signature            AlgorithmIdentifier,
     issuer               Name,
     validity             Validity,
     subject              Name,
     subjectPublicKeyInfo SubjectPublicKeyInfo,
     issuerUniqueID  [1]  IMPLICIT UniqueIdentifier OPTIONAL, -- If present, version MUST be v2 or v3
     subjectUniqueID [2]  IMPLICIT UniqueIdentifier OPTIONAL, -- If present, version MUST be v2 or v3
     extensions      [3]  EXPLICIT Extensions OPTIONAL -- If present, version MUST be v3 
     }


SubjectPublicKeyInfo  ::=  SEQUENCE  {
     algorithm            AlgorithmIdentifier,
     subjectPublicKey     BIT STRING  
     }

-- https://www.ietf.org/rfc/rfc3279.txt
-- https://stackoverflow.com/questions/43276082/how-to-use-asn-1-defined-the-x509-algorithmidentifier
AlgorithmIdentifier  ::=  SEQUENCE  {
        algorithm               OBJECT IDENTIFIER,
        parameters              ANY DEFINED BY algorithm OPTIONAL  -- Reminder: ANY is obsolete but useful for specification holes
     }

Name ::= CHOICE { -- only one possibility for now --
     rdnSequence  RDNSequence 
     }

RDNSequence ::= SEQUENCE OF RelativeDistinguishedName

RelativeDistinguishedName ::= SET OF AttributeTypeAndValue

AttributeTypeAndValue ::= SEQUENCE {
     type     AttributeType,
     value    AttributeValue 
     }

AttributeType ::= OBJECT IDENTIFIER

AttributeValue ::= CHOICE { -- ANY
     printableString PrintableString,
     utf8String UTF8String,
     ia5String IA5String 
     }

CertificateSerialNumber  ::=  INTEGER

Validity ::= SEQUENCE {
     notBefore      Time,
     notAfter       Time  
     }

Time ::= CHOICE {
     utcTime        UTCTime,
     generalTime    GeneralizedTime }

Version  ::=  INTEGER  {  v1(0), v2(1), v3(2)  }

UniqueIdentifier  ::=  BIT STRING

Extensions  ::=  SEQUENCE SIZE (1..MAX) OF Extension

-- https://www.rfc-editor.org/rfc/rfc5280.txt
Extension  ::=  SEQUENCE  {
     extnID      OBJECT IDENTIFIER,
     critical    BOOLEAN DEFAULT FALSE,
     extnValue   OCTET STRING
                    -- contains the DER encoding of an ASN.1 value
                    -- corresponding to the extension type identified
                    -- by extnID
     }





-- Elliptic curve algorithm
-- https://www.ietf.org/rfc/rfc3279.txt

EcpkParameters ::= CHOICE {
     ecParameters  ECParameters,
     namedCurve    OBJECT IDENTIFIER,
     implicitlyCA  NULL 
     }

ECParameters ::= SEQUENCE {
     version   ECPVer,          -- version is always 1
     fieldID   FieldID,         -- identifies the finite field over
                                -- which the curve is defined
     curve     Curve,           -- coefficients a and b of the
                                -- elliptic curve
     base      ECPoint,         -- specifies the base point P
                                -- on the elliptic curve
     order     INTEGER,         -- the order n of the base point
     cofactor  INTEGER OPTIONAL -- The integer h = #E(Fq)/n
     }

ECPVer ::= INTEGER {ecpVer1(1)}

FieldID ::= SEQUENCE {
     fieldType   OBJECT IDENTIFIER,
     parameters  ANY DEFINED BY fieldType -- Reminder: ANY is obsolete
     }

Curve ::= SEQUENCE {
     a         FieldElement,
     b         FieldElement,
     seed      BIT STRING OPTIONAL 
     }

FieldElement ::= OCTET STRING

ECPoint ::= OCTET STRING

END
