-- FAILS: DefinitiveIdentififier (type) contains a defined value (a)
My-Module1 { iso member-body(2) f(250) type(10) module1(1) } DEFINITIONS ::= 
BEGIN 
EXPORTS My-Integer;

My-Integer ::= INTEGER 

a INTEGER ::= 1
END
