-- FAILS: duplicate tag in SEQUENCE

Sequence DEFINITIONS IMPLICIT TAGS ::= BEGIN

Root ::= SEQUENCE {
	un BOOLEAN,
	deux BOOLEAN OPTIONAL,
	...,
	trois BOOLEAN OPTIONAL,
	...,
	quatre BOOLEAN
}



END
