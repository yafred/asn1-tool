-- FAILS: duplicate tag in SET

Set DEFINITIONS IMPLICIT TAGS ::= BEGIN

Root ::= SET {
   un BOOLEAN,
   deux INTEGER,
   trois CHOICE {
      toto IA5String,
      titi BOOLEAN
   },
...,
   [[quatre IA5String ]]
}


END
