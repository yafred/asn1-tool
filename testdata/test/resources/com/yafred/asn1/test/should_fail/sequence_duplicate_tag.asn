-- FAILS: duplicate tag (optional or default component must have distinct tags)

Sequence DEFINITIONS ::= BEGIN

T ::= SEQUENCE { 
	x INTEGER,
	y INTEGER OPTIONAL,
	z INTEGER DEFAULT 0,
	t INTEGER 
}


END
