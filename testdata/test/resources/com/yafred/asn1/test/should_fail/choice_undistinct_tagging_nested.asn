-- FAIL 
Choices DEFINITIONS ::=
BEGIN

A ::= CHOICE {
	b CHOICE {
	   un INTEGER,
	   deux IA5String
	}
	,
	c CHOICE {
	   trois INTEGER,  -- duplicate tag
	   quatre IA5String  -- duplicate tag
	} 
}

END
