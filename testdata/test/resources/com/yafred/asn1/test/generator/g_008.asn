G-008 DEFINITIONS ::= 
BEGIN 

Occupation  ::=  BIT STRING
          {
              clerk      (0),
              editor     (1),
              artist     (2),
              publisher  (3),
              multi-pass (4)
          }

Simple ::= BIT STRING

Test ::= SEQUENCE {
    bits Occupation,
    morebits Simple
}

END
