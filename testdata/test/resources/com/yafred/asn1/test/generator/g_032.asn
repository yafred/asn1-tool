G-032 DEFINITIONS ::= 
BEGIN 

Occupation  ::=  BIT STRING
          {
              clerk      (0),
              editor     (1),
              artist     (2),
              publisher  (3),
              multi-pass (4)
          }

Simple ::= BIT STRING

-- SEQUENCE of BIT STRING components
Test ::= SEQUENCE {
    bits Occupation,
    morebits Simple
}

END
