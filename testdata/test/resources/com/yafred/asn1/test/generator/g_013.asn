G-013 DEFINITIONS ::= 
BEGIN 

My-integer ::= [APPLICATION 0] INTEGER { ten(10), twenty(20) }
My-integer-list ::= SEQUENCE OF My-integer

My-string ::= [APPLICATION 1] IMPLICIT VisibleString
My-string-list ::= [APPLICATION 2] SEQUENCE OF My-string

My-octet-string ::= OCTET STRING
My-octet-string-list ::= [APPLICATION 2] SEQUENCE OF [0] IMPLICIT  My-octet-string

My-boolean ::= BOOLEAN
My-boolean-list ::= SEQUENCE OF My-boolean

My-bitstring ::= BIT STRING
          {
              clerk      (0),
              editor     (1),
              artist     (2),
              publisher  (3)
          }
My-bitstring-list ::= SEQUENCE OF My-bitstring

My-enumeration ::= ENUMERATED { banana, apple, pear, ..., lemon }
My-enumerated-list ::= SEQUENCE OF My-enumeration

My-enumeration2 ::= ENUMERATED { banana, apple, pear }
My-enumerated-list2 ::= SEQUENCE OF My-enumeration2

END
