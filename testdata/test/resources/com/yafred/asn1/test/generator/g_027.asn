G-027 DEFINITIONS AUTOMATIC TAGS ::=
BEGIN
   
   EXPORTS ALL;
   IMPORTS;
   
   Request ::= CHOICE { 
      num INTEGER,
      text IA5String
   }
   
   Response ::= CHOICE { 
      error VisibleString,
      info UTF8String
   }
   
   Message ::= CHOICE { 
      request Request, 
      response Response  
   }
   
   Message-in-sequence ::= SEQUENCE {
     info IA5String,
     request CHOICE {    
        num INTEGER,
        text IA5String
     },
     response CHOICE {   
        error VisibleString,
        info UTF8String
     }
   }
   
   Message-in-sequence-with-optional ::= SEQUENCE {
     info IA5String OPTIONAL,
     request CHOICE {   
        num INTEGER,
        text IA5String
     } OPTIONAL,
     response CHOICE {  
        error VisibleString,
        info UTF8String
     }
   }
   
   Message-in-set ::= SEQUENCE {
     info IA5String OPTIONAL,
     request CHOICE {  
        num INTEGER,
        text IA5String
     },
     response CHOICE {  
        error VisibleString,
        info UTF8String
     }
   }
   
   Message-list ::= SEQUENCE OF Message  
   
END
