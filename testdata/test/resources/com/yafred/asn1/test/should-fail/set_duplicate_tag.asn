-- FAILS: duplicate tag in SET

Set DEFINITIONS IMPLICIT TAGS ::= BEGIN

Root ::= SET {
un BOOLEAN,
deux BOOLEAN,
trois CHOICE {
    toto BOOLEAN,
    titi BOOLEAN
    },
...,
[[quatre BOOLEAN ]]
}


END
